DNDSMessage ::= SEQUENCE {
	version		INTEGER,
	channel		INTEGER,
	pdu		CHOICE {			-- Protocol Data Unit
		dnm		DNMessage,
		dsm		DSMessage,
		ethernet	BIT STRING
	}
}

DNDSResult ::= ENUMERATED {
		success				(1),
		operationError			(2),
		protocolError			(3),
		noSuchObject			(4),
		busy				(5),
		secureStepUp			(6),
		insufficientAccessRights	(7),
		moreData			(8)
}

DNMessage ::= SEQUENCE {
	seqNumber	INTEGER,
	ackNumber	INTEGER,
	dnop		CHOICE {
		authRequest		AuthRequest,
		authResponse		AuthResponse,
		netinfoRequest		NetinfoRequest,
		netinfoResponse		NetinfoResponse,
		provRequest		ProvRequest,
		provResponse		ProvResponse,
		p2pRequest		P2pRequest,
		p2pResponse		P2pResponse,
		terminateRequest	TerminateRequest
	}
}

DSMessage ::= SEQUENCE {
	seqNumber	INTEGER,
	ackNumber	INTEGER,
	dsop		CHOICE	{
		addRequest		AddRequest,
		addResponse		AddResponse,
		delRequest		DelRequest,
		delResponse		DelResponse,
		modifyRequest		ModifyRequest,
		modifyResponse		ModifyResponse,
		nodeConnectInfo		NodeConnectInfo,
		searchRequest		SearchRequest,
		searchResponse		SearchResponse,
		terminateRequest	TerminateRequest
	}
}

DNDSObject ::= CHOICE {
	client		Client,
	context		Context,
	node		Node
}

DNDSObjects ::= SEQUENCE OF DNDSObject

ObjectName ::= ENUMERATED {
	client		(1),
	context		(2),
	node		(3)
}

-------------------------
-- DN> Dynamic Network
-------------------------

AuthRequest ::= SEQUENCE {
	certName	IA5String 
}

AuthResponse ::= DNDSResult

NetinfoRequest ::= SEQUENCE {
	ipLocal		OCTET STRING ,	-- ipv4 extensible to ipv6
	macAddr		OCTET STRING 
}

NetinfoResponse ::= SEQUENCE {
	ipAddress	OCTET STRING ,
	netmask		OCTET STRING ,
	result		DNDSResult
}

ProvRequest ::= SEQUENCE {
	provCode	PrintableString OPTIONAL
}

ProvResponse ::= SEQUENCE {
	certificate	PrintableString OPTIONAL,
	certificateKey	PrintableString OPTIONAL,
	trustedCert     PrintableString OPTIONAL,
	ipAddress	OCTET STRING  OPTIONAL
}

P2pSide ::= ENUMERATED {
	client		(1),
	server		(2)
}

P2pRequest ::= SEQUENCE {
	macAddrDst	OCTET STRING ,
	ipAddrDst	OCTET STRING ,
	port		INTEGER,
	side		P2pSide
}

P2pResponse ::= SEQUENCE {
	macAddrDst	OCTET STRING ,
	result		DNDSResult
}

-------------------------
-- DS> Directory Service
-------------------------

AddRequest ::= DNDSObject
AddResponse ::= DNDSResult

DelRequest ::= DNDSObject
DelResponse ::= DNDSResult

ModifyRequest ::= DNDSObject
ModifyResponse ::= DNDSResult

ConnectState ::= ENUMERATED {
	connected	(1),
	disconnected	(2)
}

NodeConnectInfo ::= SEQUENCE {
	certName	IA5String ,
	ipAddr		OCTET STRING ,
	state		ConnectState
}

SearchType ::= ENUMERATED {
	all		(1),
	sequence	(2),
	object		(3)
}

SearchRequest ::= SEQUENCE {
	searchtype	SearchType,
	objectname	ObjectName OPTIONAL,
	object		DNDSObject OPTIONAL,
	objects		DNDSObjects OPTIONAL
}

SearchResponse ::= SEQUENCE {
	searchtype	SearchType,
	dndsResult	DNDSResult,
	objects		DNDSObjects
}

TerminateRequest ::= NULL

Topology ::= ENUMERATED {
	mesh		(1),
	hubspoke	(2),
	gateway		(3)
}

Client ::= SEQUENCE {
	id		INTEGER OPTIONAL,
	firstname	PrintableString OPTIONAL,
	lastname	PrintableString OPTIONAL,
	email		IA5String OPTIONAL,
	password	PrintableString OPTIONAL,
	company		PrintableString OPTIONAL,
	phone		PrintableString OPTIONAL,
	country		PrintableString OPTIONAL,
	stateProvince	PrintableString OPTIONAL,
	city 		PrintableString OPTIONAL,
	postalCode	PrintableString OPTIONAL,
	status		INTEGER OPTIONAL
}

Context ::= SEQUENCE {
	id		INTEGER OPTIONAL,
	clientId	INTEGER,
	topology	Topology,
	description	PrintableString  OPTIONAL,
	network         OCTET STRING ,
	netmask         OCTET STRING ,
	serverCert      PrintableString OPTIONAL,
	serverPrivkey   PrintableString OPTIONAL,
	trustedCert     PrintableString OPTIONAL
}

Node ::= SEQUENCE {
	contextId	INTEGER,
	description	PrintableString  OPTIONAL,
	uuid		PrintableString OPTIONAL,
	provCode	PrintableString OPTIONAL,
	certificate	PrintableString OPTIONAL,
	certificateKey	BIT STRING OPTIONAL,
	trustedCert     PrintableString OPTIONAL,
	ipAddress	OCTET STRING  OPTIONAL,
	status		INTEGER OPTIONAL
}
